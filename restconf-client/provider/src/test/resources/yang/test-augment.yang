module test-augment {
    yang-version 1;
    namespace "urn:opendaylight:params:xml:ns:yang:augment";
    prefix "hello";

    import test-yang {
       prefix t;
    }

    revision "2015-01-05" {
        description "Initial revision of hello model";
    }

    augment "/t:cont1/t:cont2/t:cont4" {
        container cont5 {
            leaf leaf13 {
               type string;
            }
        }
        list list7 {
           leaf leaf14 {
              type string;
           }
        }
        leaf leaf15 {
            type string;
        }
        leaf-list ll6 {
            type string;
        }
        uses "t:g1";
    }

    uses "t:g1";
    augment "/t:ch1/t:c1/t:cont8/t:cont6" {
        choice ch2 {
           case c3 {
               leaf leaf21 {
                   type string;
               }
           }
           case c4 {
               leaf leaf22 {
                   type string;
               }
           }
        }
    }

    augment "/t:ch1" {
       case c5 {
          container cont10 {
              leaf leaf23 {
                  type string;
              }
          }
       }
    }

    augment "/t:ch1/t:c1" {
        container cont7 {
            leaf leaf24 {
                type string;
            }
        }
    }

    augment "/t:cont13/t:cont12" {
       leaf leaf29 {
           type string;
       }
    }

    augment "/t:create-sfc/t:input" {
       leaf leaf36 {
           type string;
       }
    }

    augment "/t:create-sfc/t:output" {
       leaf leaf37 {
           type string;
       }
    }
}
